RestCtrl-MIB DEFINITIONS ::= BEGIN
	IMPORTS
		enterprises,
       MODULE-IDENTITY,
       OBJECT-TYPE,
       OBJECT-IDENTITY
          FROM SNMPv2-SMI
       Unsigned32,
	   Integer32,
	   Counter32,
	   TimeTicks,
	   NOTIFICATION-TYPE
	      FROM SNMPv2-SMI
	   DisplayString, TruthValue, TEXTUAL-CONVENTION
	      FROM SNMPv2-TC;

	restCtrl OBJECT IDENTIFIER ::= {enterprises 12619}
--
-- Restaurante entries
--
	capacidade OBJECT-TYPE
		SYNTAX Counter32
		MAX-ACCESS read-only
		STATUS mandatory
		DESCRIPTION "Numero de maximo de pessoas no restaurante"
	::= {restCtrl 1}

	lotAtual OBJECT-TYPE
		SYNTAX Counter32
		MAX-ACCESS read-only
		STATUS mandatory
		DESCRIPTION "Numero atual de pessoas no restaurante"
	::= {restCtrl 2}
	
	numFunc OBJECT-TYPE
		SYNTAX Counter32
		MAX-ACCESS read-only
		STATUS mandatory
		DESCRIPTION "Numero de funcionarios do restaurante"
	::= {restCtrl 6}
		
	status OBJECT-TYPE
		SYNTAX INTEGER { aberto(0), fechado(1)}
		MAX-ACCESS read-write
		STATUS mandatory
		DESCRIPTION "Status do restaurante"
	::= {restCtrl 7}

	currNumOrders OBJECT-TYPE
		SYNTAX Counter32
		MAX-ACCESS read-only
		STATUS mandatory
		DESCRIPTION "Numero de pedidos atualmente nao pronto do restaurante"
	::= {restCtrl 10}


--
-- Tabela de Pedidos diarios
--
	dailyOrdersTable OBJECT-TYPE
		SYNTAX SEQUENCE OF DailyOrdersEntry
		MAX-ACCESS not-accessible
		STATUS current
		DESCRIPTION "Numero de pedidos em um certo dia"
	::= {restCtrl 8}

	dailyOrdersEntry OBJECT-TYPE
		SYNTAX DailyOrdersEntry
		MAX-ACCESS not-accessible
		STATUS current
		DESCRIPTION "Info sobre dailyOrders" 
		INDEX { dailyOrdersIndex }
	::= {dailyOrdersTable 1}


	DailyOrdersEntry ::=	SEQUENCE {
		dailyOrdersIndex	Integer32,
		year			 	Integer32,
		month		 		Integer32,
		day					Integer32,
		orders				Integer32
	}

	dailyOrdersIndex OBJECT-TYPE
		SYNTAX Integer32 (1..2147483647)
		MAX-ACCESS read-only
		STATUS mandatory
		DESCRIPTION " The value of this object uniquely identifies this Entry."
	::= {dailyOrdersEntry 1}
	
	year OBJECT-TYPE
		SYNTAX Integer32 (1..2147483647)
		MAX-ACCESS read-only
		STATUS mandatory
		DESCRIPTION "Ano"
	::= {dailyOrdersEntry 2}

	month OBJECT-TYPE
		SYNTAX Integer32 (1..2147483647)
		MAX-ACCESS read-only
		STATUS mandatory
		DESCRIPTION "Mes"
	::= {dailyOrdersEntry 3}

	day OBJECT-TYPE
		SYNTAX Integer32 (1..2147483647)
		MAX-ACCESS read-only
		STATUS mandatory
		DESCRIPTION "dia"
	::= {dailyOrdersEntry 4}
	
	orders OBJECT-TYPE
		SYNTAX Integer32 (1..2147483647)
		MAX-ACCESS read-only
		STATUS mandatory
		DESCRIPTION "Numero de pedidos do dia"
	::= {dailyOrdersEntry 5}

--
-- Tabela de mesas
--
	mesasTable OBJECT-TYPE
		SYNTAX SEQUENCE OF MesasEntry
		MAX-ACCESS not-accessible
		STATUS current
		DESCRIPTION "Tabela contendo as informacoes das mesas"
	::= {restCtrl 3}

	mesasEntry OBJECT-TYPE
		SYNTAX MesasEntry
		MAX-ACCESS not-accessible
		STATUS current
		DESCRIPTION "Info sobre mesas" 
		INDEX { mesasIndex }
	::= {mesasTable 1}


	MesasEntry ::=	SEQUENCE {
		mesasIndex			Integer32,
		capacidadeMesa 		Integer32,
		numClientes 		Integer32,
		status				INTEGER
	}

	mesasIndex OBJECT-TYPE
		SYNTAX Integer32 (1..2147483647)
		MAX-ACCESS read-only
		STATUS mandatory
		DESCRIPTION " The value of this object uniquely identifies this Entry."
	::= {mesasEntry 1}
	
	capacidadeMesa OBJECT-TYPE
		SYNTAX Integer32 (1..2147483647)
		MAX-ACCESS read-only
		STATUS mandatory
		DESCRIPTION "Numero maximo de clientes na mesa"
	::= {mesasEntry 2}

	numClientes OBJECT-TYPE
		SYNTAX Integer32 (1..2147483647)
		MAX-ACCESS read-only
		STATUS mandatory
		DESCRIPTION "Numero clientes atualmente na mesa"
	::= {mesasEntry 3}

	status OBJECT-TYPE
		SYNTAX INTEGER{ livre(0), ocupada(1), reservada(2), indisponivel(3)}
		MAX-ACCESS read-only
		STATUS mandatory
		DESCRIPTION "Status atual da mesa"
	::= {mesasEntry 4}

--
-- Tabela de pedidos
--
	ordersTable OBJECT-TYPE
		SYNTAX SEQUENCE OF OrdersEntry
		MAX-ACCESS not-accessible
		STATUS current
		DESCRIPTION "Tabela contendo informacoes dos pedidos feitos"
	::= {restCtrl 4}

	ordersEntry OBJECT-TYPE
		SYNTAX OrdersEntry
		MAX-ACCESS not-accessible
		STATUS current
		DESCRIPTION "Info sobre pedidos" 
		INDEX { ordersIndex }
	::= {ordersTable 1}

	OrdersEntry ::=	SEQUENCE {
		ordersIndex		Integer32,
		item 			Integer32,
		table 			Integer32,
		status			INTEGER
	}
	
	ordersIndex OBJECT-TYPE
		SYNTAX Integer32 (1..2147483647)
		MAX-ACCESS read-only
		STATUS mandatory
		DESCRIPTION " The value of this object uniquely identifies this Entry."
	::= {ordersEntry 1}
	
	item OBJECT-TYPE
		SYNTAX Integer32 (1..2147483647)
		MAX-ACCESS read-only
		STATUS mandatory
		DESCRIPTION "Item do cardapio pedido"
	::= {ordersEntry 2}

	table OBJECT-TYPE
		SYNTAX Integer32 (1..2147483647)
		MAX-ACCESS read-only
		STATUS mandatory
		DESCRIPTION "Numera da mesa que fez o pedido"
	::= {ordersEntry 3}

	status OBJECT-TYPE
		SYNTAX INTEGER{ encaminhadoParaCozinha(0), emPreparo(1), pronto(2)}
		MAX-ACCESS read-only
		STATUS mandatory
		DESCRIPTION "Status atual do pedido"
	::= {ordersEntry 4}

--
-- Cardapio (Menu) Table
--
	menuTable OBJECT-TYPE
		SYNTAX SEQUENCE OF MenuEntry
		MAX-ACCESS not-accessible
		STATUS current
		DESCRIPTION "Tabela contendo os items do menu disponiveis"
	::= {restCtrl 5}

	menuEntry OBJECT-TYPE
		SYNTAX MenuEntry
		MAX-ACCESS not-accessible
		STATUS current
		DESCRIPTION "Entrada de um item no cardapio" 
		INDEX { menuIndex }
	::= {menuTable 1}

	MenuEntry ::=	SEQUENCE {
		menuIndex		Integer32,
		description		DisplayString
	}
	
	menuIndex OBJECT-TYPE
		SYNTAX Integer32 (1..2147483647)
		MAX-ACCESS read-only
		STATUS mandatory
		DESCRIPTION " The value of this object uniquely identifies this Entry."
	::= {menuEntry 1}
	
	description OBJECT-TYPE
		SYNTAX DisplayString
		MAX-ACCESS read-only
		STATUS mandatory
		DESCRIPTION "Descricao do item"
	::= {menuEntry 2}
	
--
-- Estoque Table
--
	estoqueTable OBJECT-TYPE
		SYNTAX SEQUENCE OF EstoqueEntry
		MAX-ACCESS not-accessible
		STATUS current
		DESCRIPTION "Tabela contendo os items do estoque disponiveis"
	::= {restCtrl 9}

	estoqueEntry OBJECT-TYPE
		SYNTAX EstoqueEntry
		MAX-ACCESS not-accessible
		STATUS current
		DESCRIPTION "Entrada de um item no cardapio" 
		INDEX { estoqueIndex }
	::= {estoqueTable 1}

	EstoqueEntry ::=	SEQUENCE {
		estoqueIndex		Integer32,
		name				DisplayString,
		amount				Integer32
	}
	
	estoqueIndex OBJECT-TYPE
		SYNTAX Integer32
		MAX-ACCESS read-write
		STATUS mandatory
		DESCRIPTION " The value of this object uniquely identifies this Entry."
	::= {estoqueEntry 1}
	
	name OBJECT-TYPE
		SYNTAX DisplayString
		MAX-ACCESS read-write
		STATUS mandatory
		DESCRIPTION "Descricao do item"
	::= {estoqueEntry 2}
	
	amount OBJECT-TYPE
		SYNTAX Integer32
		MAX-ACCESS read-write
		STATUS mandatory
		DESCRIPTION "Quantidade ainda disponivel, em kg"
	::= {estoqueEntry 3}
	
	
--
-- Traps
--
estoqueTrap	OBJECT IDENTIFIER ::= { restCtrl 11 }

estoqueItemChange NOTIFICATION-TYPE
    OBJECTS { estoqueIndex, name, amount }
    STATUS  current
    DESCRIPTION
        "A estoqueTrap trap signifies that the estoque has changed."
    ::= { estoqueTrap 1 }


	
	
END
